# TestRequirements

## #1: Signal Range Requirements (Functional)
Just setting up mock requirements for testing Simulink testing, coverage and requirements blocks.

### #3: max(sign(force-signals)) <= 300 N (Functional)

### #4: max(derivate(force-signal)) <= 5 N/s (Functional)
